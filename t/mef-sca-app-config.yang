module mef-sca-app-config {
  namespace "urn:mef-sca-app-config";
  prefix mef-sca-app;

  organization "Metro Ethernet Forum";
  contact
    "TODO";
  description
    "MEF SCA Application Settings API";

  revision 2015-11-18 {
    description
      "First revision of sca-app settings";
  }

  container settings {
      leaf service-driver {
          type enumeration {
              enum "ncs-epl" {
                  description "Delegate service implementation to Tail-f NCS using EPL";
              }
              enum "ncs-evpl" {
                  description "Delegate service implementation to Tail-f NCS using EVPL";
              }
              enum "odl" {
                  description "Perform service decomposition in ODL";
              }
          }
      }
      
      leaf activation-driver {
          type enumeration {
              enum "l2vpn-xconnect" {
                  description "Use l2vpn xconnect";
              }
              enum "vpls" {
                  description "Use VPLS";
              }
              enum "external" {
                  description "Implemented externally.";
              }
          }
      }
  }
}
